module polycube-base {
  yang-version 1.1;
  namespace "http://polycube.network/polycube-base";
  prefix "polycube-base";

  organization "Polycube open source project";

  description "This YANG module describes the base configuration model
  for a polycube service. In particular, it contains the definition of:
    1. Unique identifier (UUID) of each Cube
    2. Type of each Cube
    3. Ports of an Cube";

  extension cli-example {
    argument "value";
    description "A sample value used by the CLI generator";
  }

  typedef polycube-uuid {
    type string {
      pattern '[0-9a-f]{8}-[0-9a-f]{4}-[1-5][0-9a-f]{3}-[89ab][0-9a-f]{3}-[0-9a-f]{12}';
    }
    description "UUID of the cube";
  }

  extension polycube-class {
    argument "value";
    description "The corresponding C++ class used by the polycube framework";
  }

  extension service-description {
    argument "value";
    description "The description of the service that is shown in the CLI";
  }

  extension service-version {
    argument "value";
    description "Current version of the service data model";
  }

  extension service-name {
    argument "value";
    description "Name of the service used in the CLI";
  }

  extension service-min-kernel-version {
    argument "value";
    description "Minimum kernel version required by the service. Format is x.y.z (e.g. 4.13.1, 4.14.0)";
  }

  extension init-only-config {
    description "TODO";
  }

  grouping base-yang-module {
    leaf uuid {
      type polycube-uuid;
      config false;
      description "UUID of the Cube";
    }

    leaf type {
      type enumeration {
        enum TC;
        enum XDP_SKB;
        enum XDP_DRV;
      }
      config true;
      default TC;
      modelbase:init-only-config;
      description "Type of the Cube (TC, XDP_SKB, XDP_DRV)";
      polycube-base:cli-example "TC";
    }

    leaf loglevel {
      type enumeration {
        enum TRACE;
        enum DEBUG;
        enum INFO;
        enum WARN;
        enum ERR;
        enum CRITICAL;
        enum OFF;
      }
      default INFO;
      description "Defines the logging level of a service instance, from none (OFF) to the most verbose (TRACE)";
      polycube-base:cli-example "INFO";
    }
  }
}
